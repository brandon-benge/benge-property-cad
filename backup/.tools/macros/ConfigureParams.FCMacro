import importlib
from freecad_macro_tools import macro_actions

importlib.reload(macro_actions)
macro_actions.load_project_params_env()

try:
    macro_actions.configure_project_params()
except Exception as exc:
    macro_actions.show_error("Configure Parameters Failed", str(exc))
    raise
