import os
import runpy
import sys

HERE = os.path.dirname(os.path.abspath(__file__))
TOOLS_DIR = os.path.join(HERE, ".tools")
if TOOLS_DIR not in sys.path:
    sys.path.insert(0, TOOLS_DIR)
runpy.run_path(os.path.join(HERE, ".tools", "macros", "InitRepo.FCMacro"))
