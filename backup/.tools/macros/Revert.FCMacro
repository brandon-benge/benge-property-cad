import importlib
from freecad_macro_tools import build, macro_actions

importlib.reload(build)
importlib.reload(macro_actions)
macro_actions.load_project_params_env()

try:
    macro_actions.revert_last_commit_and_push()
    build.rebuild()
except Exception as exc:
    macro_actions.show_error("Revert Failed", str(exc))
    raise
